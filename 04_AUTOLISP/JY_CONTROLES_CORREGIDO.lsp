; Base corregida; conserva la dependencia Windows/ActiveX. Pendiente de prueba real en AutoCAD.
;;; JY_CONTROLES - controles sobre bloques convencionales con atributos.
;;; No crea bloques dinamicos nativos ni acciones de Block Editor.
;;; Requiere AutoCAD para Windows con AutoLISP/ActiveX. Trabajar en Modelo.
;;; Archivo preparado sin prueba de ejecucion en AutoCAD.
(vl-load-com)
(setq JY:catalogo
 '(("CAJA"
    ("JY_CP_100X100X50" "A - 100x100x50" (("CODIGO" . "A1") ("DIMENSION" . "100x100x50 mm")))
    ("JY_CP_150X150X100" "B - 150x150x100" (("CODIGO" . "B1") ("DIMENSION" . "150x150x100 mm")))
    ("JY_CP_200X200X100" "C - 200x200x100" (("CODIGO" . "C1") ("DIMENSION" . "200x200x100 mm")))
    ("JY_CP_300X300X150" "D - 300x300x150" (("CODIGO" . "D1") ("DIMENSION" . "300x300x150 mm")))
    ("JY_CP_400X400X150" "E - 400x400x150" (("CODIGO" . "E1") ("DIMENSION" . "400x400x150 mm")))
    ("JY_CP_600X400X200" "F - 600x400x200" (("CODIGO" . "F1") ("DIMENSION" . "600x400x200 mm"))))
   ("NORMAL"
    ("JY_TN_M_040" "Muro h=0.40 m" (("TIPO" . "T-01") ("ALTURA" . "+0.40 m") ("SISTEMA" . "NORMAL") ("MONTAJE" . "M") ("DGE" . "")))
    ("JY_TN_M_120" "Muro h=1.20 m" (("TIPO" . "T-01 / H120") ("ALTURA" . "+1.20 m") ("SISTEMA" . "NORMAL") ("MONTAJE" . "M") ("DGE" . "")))
    ("JY_TN_EST_110" "Estanco h=1.10 m" (("TIPO" . "T-02") ("ALTURA" . "+1.10 m") ("SISTEMA" . "NORMAL") ("MONTAJE" . "M") ("DGE" . "")))
    ("JY_TN_PISO" "Piso" (("TIPO" . "T-03") ("ALTURA" . "NPT +/-0.00") ("SISTEMA" . "NORMAL") ("MONTAJE" . "P") ("DGE" . "")))
    ("JY_TN_MES_110" "Mesada h=1.10 m" (("TIPO" . "T-04") ("ALTURA" . "+1.10 m") ("SISTEMA" . "NORMAL") ("MONTAJE" . "M") ("DGE" . "")))
    ("JY_TN_MES_120" "Mesada h=1.20 m" (("TIPO" . "T-04 / H120") ("ALTURA" . "+1.20 m") ("SISTEMA" . "NORMAL") ("MONTAJE" . "M") ("DGE" . "")))
    ("JY_TN_TECHO" "Techo" (("TIPO" . "TN / TECHO") ("ALTURA" . "EN TECHO") ("SISTEMA" . "NORMAL") ("MONTAJE" . "T") ("DGE" . ""))))
   ("ESTABILIZADO"
    ("JY_TE_M_040" "Muro h=0.40 m" (("TIPO" . "E-01") ("ALTURA" . "+0.40 m") ("SISTEMA" . "ESTABILIZADO") ("MONTAJE" . "M") ("DGE" . "")))
    ("JY_TE_M_120" "Muro h=1.20 m" (("TIPO" . "E-01 / H120") ("ALTURA" . "+1.20 m") ("SISTEMA" . "ESTABILIZADO") ("MONTAJE" . "M") ("DGE" . "")))
    ("JY_TE_PISO" "Piso" (("TIPO" . "E-03") ("ALTURA" . "NPT +/-0.00") ("SISTEMA" . "ESTABILIZADO") ("MONTAJE" . "P") ("DGE" . "")))
    ("JY_TE_AV_TECHO" "Audiovisual en techo" (("TIPO" . "E-04 / T") ("ALTURA" . "EN TECHO") ("SISTEMA" . "ESTABILIZADO") ("MONTAJE" . "T") ("DGE" . "")))
    ("JY_TE_AV_220" "Pantalla h=2.20 m" (("TIPO" . "E-04 / H220") ("ALTURA" . "+2.20 m") ("SISTEMA" . "ESTABILIZADO") ("MONTAJE" . "M") ("DGE" . "")))
    ("JY_TE_AV_120" "Dispensador h=1.20 m" (("TIPO" . "E-04 / H120") ("ALTURA" . "+1.20 m") ("SISTEMA" . "ESTABILIZADO") ("MONTAJE" . "M") ("DGE" . "")))
    ("JY_TE_ESP_040" "Salida especial" (("TIPO" . "E-05") ("ALTURA" . "+0.40 m") ("SISTEMA" . "ESTABILIZADO") ("MONTAJE" . "M") ("DGE" . ""))))))
(defun JY:doc () (vla-get-ActiveDocument (vlax-get-acad-object)))
(defun JY:modelo ()
 (if (> (getvar "CVPORT") 1) T
  (progn (princ "\nEjecute el comando en Modelo o dentro de una ventana de Modelo.") nil)))
(defun JY:elegir (/ fam opts i n)
 (initget "Caja Normal Estabilizado")
 (setq fam (getkword "\nFamilia [Caja/Normal/Estabilizado] <Caja>: "))
 (if (not fam) (setq fam "Caja"))
 (setq opts (cdr (assoc (strcase fam) JY:catalogo)) i 0)
 (foreach item opts
  (setq i (1+ i)) (princ (strcat "\n" (itoa i) ". " (cadr item))))
 (setq n nil)
 (while (not n)
  (initget 6) (setq n (getint "\nTipo <1>: "))
  (if (not n) (setq n 1))
  (if (> n (length opts)) (progn (princ "\nNumero fuera de lista.") (setq n nil))))
 (nth (1- n) opts))
(defun JY:atributos (obj / res)
 (setq res nil)
 (if (= (vla-get-HasAttributes obj) :vlax-true)
  (foreach at (vlax-invoke obj 'GetAttributes)
   (setq res (cons (cons (strcase (vla-get-TagString at)) (vla-get-TextString at)) res)))) res)
(defun JY:poner (obj vals)
 (if (= (vla-get-HasAttributes obj) :vlax-true)
  (foreach at (vlax-invoke obj 'GetAttributes)
   (if (assoc (strcase (vla-get-TagString at)) vals)
    (vla-put-TextString at (cdr (assoc (strcase (vla-get-TagString at)) vals)))))))
(defun JY:horizontal (obj)
 (if (= (vla-get-HasAttributes obj) :vlax-true)
  (foreach at (vlax-invoke obj 'GetAttributes) (vla-put-Rotation at 0.0))))
(defun JY:angulo (ang)
 (angle '(0.0 0.0 0.0) (trans (polar '(0.0 0.0 0.0) ang 1.0) 1 0 T)))
(defun JY:crear (entry pt sx sy sz ang / doc lay obj)
 (if (not (tblsearch "BLOCK" (car entry)))
  (progn (princ "\nBloque no cargado. Abra PLANTILLA_IE.dxf o copie primero ese bloque desde la plantilla.") nil)
  (progn
   (setq doc (JY:doc)
    lay (cond ((wcmatch (car entry) "JY_TN_*") "IE-TOM-N")
              ((wcmatch (car entry) "JY_TE_*") "IE-TOM-E") (T "IE-CAJAS")))
   (if (not (tblsearch "LAYER" lay)) (vla-Add (vla-get-Layers doc) lay))
   (setq obj (vla-InsertBlock (vla-get-ModelSpace doc) (vlax-3d-point pt) (car entry) sx sy sz ang))
   (vla-put-Layer obj lay) (JY:poner obj (caddr entry)) (JY:horizontal obj) obj)))
(defun JY:seleccionar (/ en ob)
 (setq en (car (entsel "\nSeleccione un bloque de la plantilla: ")))
 (if (and en (= (cdr (assoc 0 (entget en))) "INSERT"))
  (progn (setq ob (vlax-ename->vla-object en))
   (if (wcmatch (strcase (vla-get-Name ob)) "JY_*") ob
    (progn (princ "\nEl bloque no pertenece a esta biblioteca JY_.") nil)))
  (progn (princ "\nNo se selecciono una referencia de bloque.") nil)))
(defun c:JYINSERTA (/ entry pt ang sc obj cod)
 (if (JY:modelo)
  (progn
   (setq entry (JY:elegir) pt (getpoint "\nPunto de insercion: "))
   (if pt
    (progn
     (setq ang (getangle pt "\nGiro <0>: ")) (if (not ang) (setq ang 0.0))
     (initget 6) (setq sc (getreal "\nEscala grafica <1 para 1:50>: ")) (if (not sc) (setq sc 1.0))
     (setq obj (JY:crear entry (trans pt 1 0) sc sc sc (JY:angulo ang)))
     (if (and obj (assoc "CODIGO" (caddr entry)))
      (progn (setq cod (getstring T "\nCodigo interior <conservar>: "))
       (if (/= cod "") (JY:poner obj (list (cons "CODIGO" (strcase cod))))))))))) (princ))
(defun c:JYMUEVE (/ obj old pt)
 (if (and (JY:modelo) (setq obj (JY:seleccionar)))
  (progn (setq old (vlax-get obj 'InsertionPoint)
   pt (getpoint (trans old 0 1) "\nNueva posicion: "))
   (if pt (vla-Move obj (vlax-3d-point old) (vlax-3d-point (trans pt 1 0)))))) (princ))
(defun c:JYGIRA (/ obj base ang)
 (if (and (JY:modelo) (setq obj (JY:seleccionar)))
  (progn (setq base (vlax-get obj 'InsertionPoint)
   ang (getangle (trans base 0 1) "\nNuevo giro absoluto: "))
   (if ang
    (progn (vla-Rotate obj (vlax-3d-point base) (- (JY:angulo ang) (vla-get-Rotation obj)))
     (JY:horizontal obj))))) (princ))
(defun c:JYTIPO (/ obj entry vals nuevo keep oldcode newcode)
 (if (and (JY:modelo) (setq obj (JY:seleccionar)))
  (progn
   (setq entry (JY:elegir) vals (JY:atributos obj))
   (setq nuevo (JY:crear entry (vlax-get obj 'InsertionPoint)
     (vla-get-XScaleFactor obj) (vla-get-YScaleFactor obj) (vla-get-ZScaleFactor obj) (vla-get-Rotation obj)))
   (if nuevo
    (progn
     (setq keep nil)
     (foreach key '("TABLERO" "CIRCUITO" "MATERIAL" "IP")
      (if (assoc key vals) (setq keep (cons (assoc key vals) keep))))
     (setq oldcode (cdr (assoc "CODIGO" vals)) newcode (cdr (assoc "CODIGO" (caddr entry))))
     (if (and oldcode newcode (> (strlen oldcode) 1) (wcmatch (substr oldcode 2) "#*"))
      (setq keep (cons (cons "CODIGO" (strcat (substr newcode 1 1) (substr oldcode 2))) keep)))
     (JY:poner nuevo keep) (vla-Delete obj) (JY:horizontal nuevo)))))(princ))
(princ "\nJY: JYINSERTA, JYMUEVE, JYGIRA, JYTIPO. Bloques convencionales con atributos; no dinamicos nativos.")
(princ)
